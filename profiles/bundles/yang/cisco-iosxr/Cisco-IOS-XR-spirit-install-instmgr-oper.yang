module Cisco-IOS-XR-spirit-install-instmgr-oper {

  /*** NAMESPACE / PREFIX DEFINITION ***/

  namespace "http://cisco.com/ns/yang"+
    "/Cisco-IOS-XR-spirit-install-instmgr-oper";


  prefix "spirit-install-instmgr-oper";

  /*** LINKAGE (IMPORTS / INCLUDES) ***/

  import Cisco-IOS-XR-types { prefix "xr"; }

  import cisco-semver { prefix "semver"; }

  include Cisco-IOS-XR-spirit-install-instmgr-oper-sub2 {
    revision-date 2020-10-06;
  }

  include Cisco-IOS-XR-spirit-install-instmgr-oper-sub1 {
    revision-date 2020-10-06;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR spirit-install-instmgr package operational data.

     This module contains definitions
     for the following management objects:
       install: Install operations info

     Copyright (c) 2013-2020 by Cisco Systems, Inc.
     All rights reserved.";

  revision "2020-10-06" {
    description
      "Fixing backward compatible addition of new leafs.";
    semver:module-version "3.0.0";
  }

  revision "2020-03-03" {
    description
      "Fixing schema-describe support.
2019-06-28
Common yang action model between lindt and eXR install.";
    semver:module-version "2.1.0";
  }

  revision "2019-04-05" {
    description
      "Establish semantic version baseline.";
    semver:module-version "2.0.0";
  }

  revision "2018-11-29" {
    description
      "Structured the yang response for show CLIs.";
  }

  revision "2018-08-24" {
    description
      "Changed model structure for software version and deprecated img-info node.";
  }

  revision "2017-09-07" {
    description
      "Fixed type translation error.";
  }

  revision "2017-07-24" {
    description
      "Fixing backward compatibility error in module.";
  }

  revision "2015-11-09" {
    description
      "IOS XR 6.0 revision.";
  }

  grouping SUMMARY {
    description "Common node of committed, active";

    container summary {
      description "Summary information";
      uses INST-SUMMARY-PACKAGES-BAG;
    }
  }

  grouping NODE-TABLE {
    description "Common node of active, committed";

    container nodes {
      description "Table for per-node package data";

      list node {
        key "node";
        description "Per-node package data";
        leaf node {
          type xr:Node-id;
          description "Node name";
        }
        uses INST-PACKAGES-BAG;
      }
    }
  }

  container install {
    config false;
    description "Install operations info";


    container request-str {
      description "Show current request";
      uses CURRENT-INSTALL-OPERATION;
    }

    container superseded {
      description "Show superseded packages";
      uses INSTMGR-SHOW-INST-SUPERSEDED;
    }

    container inactives-str {
      description "Show XR inactive packages";
      uses INSTALL-LOG;
    }

    container valid-log-id {
      description "Show valid log ids for XR";
      uses INSTMGR-SHOW-VALID-LOGID;
    }

    container supersede-str {
      description "Show superseded packages";
      uses INSTMGR-SHOW-INST-SUP;
    }

    container package-xr {
      description "Show the list of installed packages";

      list package {
        key "package-name";
        description "Show the info for a installed package";

        container verbose {
          description
            "Show the verbose info for a installed package";
          uses INSTALL-LOG;
        }

        container brief {
          description "Show the info for a installed package";
          uses INSTALL-LOG;
        }

        container detail {
          description
            "Show the deatil info for a installed package";
          uses INSTALL-LOG;
        }
        leaf package-name {
          type string {
            length "1..256";
          }
          description "Package name";
        }
      }
    }

    container inactives-summary-str {
      description "Show XR inactive packages";
      uses INSTALL-LOG;
    }

    container inactive-summary {
      description "Show XR inactive packages";
      uses INSTMGR-SHOW-INST-INACTIVE;
    }

    container committed-summary-str {
      description "Show Committed packages installed";
      uses INSTMGR-CALV-SHOW-INST-COMMIT;
    }


    container prepare {
      description "Show prepared packages ready for activation";
      uses INSTMGR-YANG-SHOW-INSTALL-PREPARE;
    }

    container active-summary-str {
      description "Show active packages installed";
      uses INSTMGR-CALV-SHOW-INST-ACT;
    }

    container packages {
      description "Show packages installed";

      container active {
        description "Information about active packages";
        uses NODE-TABLE;
        uses SUMMARY;
      }

      container committed {
        description "Information about committed packages";
        uses NODE-TABLE;
        uses SUMMARY;
      }
    }

    container version {
      description "Show install version";
      uses INST-VERSION-BAG;
    }

    container repository {
      description "Show install repository all";
      uses INSTMGR-SHOW-INST-REPO;
    }

    container inactive {
      description "Show XR inactive packages";
      uses INSTMGR-SHOW-INST-INACTIVE;
    }

    container request {
      description "Show current request";
      uses INST-REQUEST-BAG;
    }

    container supersededsummary-str {
      description "Show superseded packages";
      uses INSTALL-LOG;
    }

    container superseded-summary {
      description "Show superseded summary packages";
      uses INSTMGR-SHOW-INST-SUP-SUMMARY;
    }

    container issu {
      description "ISSU operation";

      container stage {
        description "Show XR install issu stage";
        uses ISD-STAGE-INFO;
      }

      container inventory {
        description "Show XR install issu inventory";
        uses ISD-INV-INFO-CONTAINER;
      }
    }

    container committed-str {
      description "Show Committed packages installed";
      uses INSTMGR-CALV-SHOW-INST-COMMIT;
    }

    container last-operation-log {
      description "It shows the log of last operation performed";
      uses INSTMGR-SHOW-INST-LOG;
    }

    container admin-packages {
      description "Show packages installed";

      container admin-active-summary {
        description "Show Calvados Active packages summary";
        uses INST-ALL-PACKAGES-BAG;
      }

      container admin-active {
        description "Show calvados active packages installed";
        uses INST-ALL-PACKAGES-BAG;
      }

      container admin-committed-summary {
        description "Show Calvados Committed packages summary";
        uses INST-ALL-PACKAGES-BAG;
      }

      container admin-inactive {
        description "Show calvados inactive packages";
        uses INSTMGR-SHOW-INST-INACTIVE;
      }

      container admin-committed {
        description "Show Calvados Committed packages installed";
        uses INST-ALL-PACKAGES-BAG;
      }

      container admin-inactive-summary {
        description "Show calvados inactive packages";
        uses INSTMGR-SHOW-INST-INACTIVE;
      }

      container admin-superseded {
        description "Show calvados superseded packages";
        uses INST-ALL-PACKAGES-BAG;
      }
    }

    container version-str {
      description "Show install version";
      uses INST-VERSION-BAG;
    }

    container prepare-str {
      description "Show prepared packages ready for activation";
      uses INSTMGR-SHOW-INSTALL-PREPARE;
    }

    container active-str {
      description "Information about active packages";
      uses INSTMGR-CALV-SHOW-INST-ACT;
    }

    container operation-logs {
      description "Show log file";

      list operation-log {
        key "operation-id";
        description "Show log file for the specified install ID";
        leaf operation-id {
          type uint32 {
            range "0..134217728";
          }
          description "Op ID number";
        }
        uses INSTMGR-SHOW-INST-LOG;
      }
    }
  }
}
