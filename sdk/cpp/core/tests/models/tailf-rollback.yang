module tailf-rollback {
  yang-version 1.1;
  namespace "http://tail-f.com/ns/rollback";
  prefix rollback;

  // This module is explicitly exported only to those interfaces that
  // do not have their own rollback API (like e.g. the CLI which has
  // its own builtin commands to handle rollbacks)

  tailf:export rest;
  tailf:export netconf;
  tailf:export maapi;

  import ietf-yang-types {
    prefix yang;
  }

  import tailf-common {
    prefix tailf;
  }

  organization "Tail-f Systems";

  description
    "This module defines a data model for rollback file handling.

     Copyright 2019 Cisco Systems, Inc.
     All rights reserved.
     Permission is hereby granted to redistribute this file without
     modification.";

  revision 2018-01-12 {
    description
      "Released as part of ConfD-6.4.5 / NCS-4.4.5.

       Exported to NETCONF and maapi.

       Made the input id parameter mandatory (as it already was, but
       not explicitly).

       Added selective and path input parameters to
       apply-rollback-file action.";
 }

  revision 2016-09-15 {
    description
        "Initial release.";
  }

  container rollback-files {
    config false;
    tailf:info "Rollback file handling";

    tailf:callpoint "rbagent" {
      tailf:internal;
    }

    list file {
      key id;
      description
        "Rollback file information.";

      leaf id {
        type uint32;
        description
          "Identifier for a rollback file.";
      }
      leaf name {
        type string;
        description
          "Filename of the rollback file.";
      }
      leaf fixed-number {
        type uint64;
        description
          "The number of this rollback files. This number doesn't
           change and can be used as input to the get- and apply-
           actions defined in this module.";
      }
      leaf creator {
        type string;
        description
          "The user which caused the rollback file to be created.";
      }
      leaf date {
        type string;
        description
          "Date for the creation of the rollback file.";
      }
      leaf via {
        type string;
        description
          "What interface was used when the rollback file was created.";
      }
      leaf label {
        type string;
        description
          "A label.";
      }
      leaf comment {
        type string;
        description
          "A comment.";
      }
    }

    grouping rollback-reference {
      choice rollback {
        mandatory true;
        leaf id {
          description "The identifier of the rollback file.";
          type leafref {
            path "/rollback-files/file/id";
          }
        }
        leaf fixed-number {
          description "The fixed-number of the rollback file.";
          type leafref {
            path "/rollback-files/file/fixed-number";
          }
        }
      }
    }

    action get-rollback-file {
      description
        "Get the content of a specific rollback file.";

      tailf:actionpoint rbagent {
        tailf:internal;
      }
      input {
        uses rollback-reference;
      }
      output {
        leaf content {
          type string;
        }
      }
    }

    action apply-rollback-file {
      description
        "Apply a specific rollback file.";

      tailf:actionpoint rbagent {
        tailf:internal;
      }

      input {
        uses rollback-reference;
        leaf selective {
          type empty;
          description
            "Only apply the changes in this particular rollback file.";
        }
        leaf path {
          type yang:xpath1.0;
          description
            "Only apply changes for the sub tree restricted by this path.";
        }
      }
    }

  }
}
